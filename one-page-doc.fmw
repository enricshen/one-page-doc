FME workspace one-page-doc.fmw

Parameters:
- AGOL_PORTAL = AGOL   # ArcGIS Online,AGOL%Portal,PORTAL ArcGIS Online or Portal
- Username =
- Password =
- Query =
- ArcGIS_URL =   # URL for your Organisation
- DestDataset_HTML = D:\Users\enric\Documents\MEGA\My Projects\FME Templates\AGOL\one-page-doc.html   # Destination Html File

Writers:
- HTML_1: HTML to $(DestDataset_HTML)

Creator
    GEOMTYPE = Geometry Object
    NUM = 1
    CREATED -> Tester
Note: AGOL or Portal
Tester
    BOOL_OP = OR
    TEST_CLAUSE = TEST $(AGOL_PORTAL) = AGOL
    TEST_MODE = TEST
    PASSED -> HTTPCaller
    PASSED -> AttributeManager_2
    PASSED -> AttributeManager_9
    FAILED -> HTTPCaller_3
    FAILED -> AttributeManager_2
    FAILED -> AttributeManager_9
Note: Set doc header
AttributeManager_2
    ATTR_TABLE:
      SET_TO doc_header = <!DOCTYPE html>
        <html lang="en">
        <head>
            <title>One Page Layer Catalogue</title>

            <!-- Meta -->
            <meta charset="utf-8">
            <meta http-equiv="X-UA-Compatible" content="IE=edge">
            <meta name="viewport" content="width=device-width, initial-scale=1.0">

            <meta name="description" content="One Page Layer Catalogue for ArcGIS Online or ArcGIS Enterprise Portal Items. Produced from FME Workbench using ArcGIS
            REST API">
            <meta name="author" content="Enric Shen">
            <link rel="shortcut icon" href="favicon.ico">

            <!-- Google Font -->
            <link href="https://fonts.googleapis.com/css?family=Poppins:300,400,500,600,700&display=swap" rel="stylesheet">

            <!-- FontAwesome JS-->
            <script defer src="https://cdnjs.cloudflare.com/ajax/libs/font-awesome/6.1.1/js/all.min.js"></script>

            <!-- Theme CSS -->
             <style>
            /*!
         * Bootstrap v5.2.0-beta1 (https://getbootstrap.com/)
         * Copyright 2011-2022 The Bootstrap Authors
         * Copyright 2011-2022 Twitter, Inc.
         * Licensed under MIT (https://github.com/twbs/bootstrap/blob/main/LICENSE)
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        */body{font-family:Poppins,sans-serif;-webkit-font-smoothing:antialiased;-moz-osx-font-smoothing:grayscale;color:#5d6778;padding-top:69px}.h1,.h2,.h3,.h4,.h5,.h6,h1,h2,h3,h4,h5,h6{font-family:Poppins,sans-serif;color:#252930;font-weight:600}code{background:#f4fcf6;color:#252930;padding:.25rem .375rem;border-radius:.25rem}.table td,.table th{border-color:#e7e9ed}.table thead th{border-color:#e7e9ed}.table-striped tbody tr:nth-of-type(odd){background-color:#f5f5f5}.table-dark td,.table-dark th,.table-dark thead th{border-color:#515a6a}.popover{border-color:#e0f7e6}.bs-popover-auto[x-placement^=left]>.arrow::before,.bs-popover-left>.arrow::before{border-left-color:#e0f7e6}.bs-popover-auto[x-placement^=right]>.arrow::before,.bs-popover-right>.arrow::before{border-right-color:#e0f7e6}.bs-popover-auto[data-popper-placement^=top]>.arrow::before,.bs-popover-auto[x-placement^=top]>.arrow::before,.bs-popover-top>.arrow::before{border-top-color:#e0f7e6}.bs-popover-auto[data-popper-placement^=bottom]>.arrow::before,.bs-popover-auto[x-placement^=bottom]>.arrow::before,.bs-popover-bottom>.arrow::before{border-bottom-color:#e0f7e6}a.theme-link{color:#252930;text-decoration:underline;-webkit-text-decoration-color:rgba(37,41,48,.3);text-decoration-color:rgba(37,41,48,.3)}a.theme-link:hover{color:#28b76b;-webkit-text-decoration-color:rgba(40,183,107,.8);text-decoration-color:rgba(40,183,107,.8)}a.text-link{text-decoration:none}a.text-link:hover{text-decoration:underline}.btn{font-weight:600;padding:.6rem 1.25rem;border:none}.btn:active,.btn:focus,.btn:hover{box-shadow:0 5px 15px 0 rgba(0,0,0,.15);box-shadow:0 12px 24px -6px rgba(0,0,0,.15);text-decoration:none;outline:0;transition:all .4s ease-in-out}@media (prefers-reduced-motion:reduce){.btn:active,.btn:focus,.btn:hover{transition:none}}.btn.focus,.btn:focus{box-shadow:none!important}.btn-primary{background:#28b76b;color:#fff}.btn-primary:active,.btn-primary:focus,.btn-primary:hover{color:#fff}.btn-secondary{background:#5d6778;color:#fff}.btn-light{background:#f4fcf6;color:#28b76b}.btn-light:hover{background:#f4fcf6;color:#28b76b}.form-control{padding-top:.875rem;padding-bottom:.875rem;height:2.75rem;border-color:#e0f7e6}.form-control:focus{box-shadow:0 5px 15px 0 rgba(0,0,0,.15);outline:0}.theme-icon-holder{display:inline-block;background:#f4fcf6;color:#28b76b;width:32px;height:32px;padding-top:4px;font-size:1rem;text-align:center;border-radius:50%}.theme-icon-holder .svg-inline---fa{color:#28b76b}.theme-bg-light{background:#f4fcf6}.theme-bg-dark{background:#28b76b}.theme-bg-shapes-right{position:absolute;height:100%;width:100%;right:0;top:0;overflow:hidden}.theme-bg-shapes-right:before{content:"";width:300px;height:150px;background:rgba(255,255,255,.1);position:absolute;right:-60px;top:0;border-radius:4px;-webkit-transform:skew(25deg,-10deg);transform:skew(25deg,-10deg);moz-transform-origin:top left;-webkit-transform-origin:top left;transform-origin:top left}.theme-bg-shapes-right:after{content:"";width:150px;height:600px;background:rgba(255,255,255,.15);position:absolute;right:0;top:30px;border-radius:6px;-webkit-transform:skew(25deg,10deg);transform:skew(25deg,10deg);moz-transform-origin:top left;-webkit-transform-origin:top left;transform-origin:top left}.theme-bg-shapes-left{position:absolute;height:100%;width:100%;right:0;top:0;overflow:hidden}.theme-bg-shapes-left:before{content:"";width:300px;height:150px;background:rgba(255,255,255,.1);position:absolute;left:-90px;top:0;border-radius:6px;-webkit-transform:skew(25deg,-12deg);transform:skew(25deg,-12deg);moz-transform-origin:top left;-webkit-transform-origin:top left;transform-origin:top left}.theme-bg-shapes-left:after{content:"";width:150px;height:600px;background:rgba(255,255,255,.15);position:absolute;left:0;top:30px;border-radius:4px;-webkit-transform:skew(-25deg,10deg);transform:skew(-25deg,10deg);moz-transform-origin:top left;-webkit-transform-origin:top left;transform-origin:top left}.border-radius-0{border-radius:0}.font-style-normal{font-style:normal!important}.single-col-max{max-width:800px}.site-logo .logo-text{color:#252930;font-size:1.5rem;font-weight:700}.site-logo .text-alt{font-weight:300}.site-logo .org-text{font-weight:200}.site-logo .navbar-brand{font-size:2rem;font-weight:600;padding-top:0}.page-header.theme-bg-dark .page-heading{color:#fff}.page-header.theme-bg-dark .page-intro{color:#fff;-webkit-opacity:.8;-moz-opacity:.8;opacity:.8}.social-list li{font-size:1.125rem;background:#f4fcf6;width:32px;height:32px;text-align:center;border-radius:50%;padding-top:2px}.social-list li a{color:#3dd584}.social-list li a:hover{color:#28b76b}.social-list li:not(:last-child){margin-right:.875rem}.header{box-shadow:0 1px 4px 0 rgba(0,0,0,.1);background:#fff}.btn-danger,.btn-info,.btn-success,.btn-warning{color:#fff}.btn-danger:active,.btn-danger:focus,.btn-danger:hover,.btn-info:active,.btn-info:focus,.btn-info:hover,.btn-success:active,.btn-success:focus,.btn-success:hover,.btn-warning:active,.btn-warning:focus,.btn-warning:hover{color:#fff}.footer .copyright{font-size:.875rem}.page-heading{font-size:2.5rem}.page-intro{font-size:1.125rem}.main-search-box{max-width:600px}.docs-overview .card{border-color:#e7e9ed;position:relative;height:100%}.docs-overview .card:hover{box-shadow:0 .5rem 1rem rgba(0,0,0,.15)!important;background:#f4fcf6}.docs-overview .card:hover .card-icon-holder{background:#fff}.docs-overview .card-icon-holder{width:60px;height:60px;font-size:1.5rem;padding-top:1rem;display:inline-block}.docs-overview .card-title-text{display:inline-block;position:relative;top:-.3rem}.docs-overview .card-link-mask{position:absolute;width:100%;height:100%;top:0;left:0}.search-form{position:relative;width:100%}.search-form .search-input{font-size:.875rem;border-radius:1.5rem;padding-right:3rem;padding-left:1.5rem}.search-form .search-input:focus{border-color:#e7e9ed}.search-form .search-btn{color:#828d9f;background:0 0;border:none;position:absolute;right:0;top:.15rem;margin-right:0}.search-form .search-btn:active,.search-form .search-btn:focus,.search-form .search-btn:hover{outline:0!important;color:#28b76b;box-shadow:none}.docs-branding{min-height:69px}.docs-branding .top-search-box{width:300px}.docs-logo-wrapper{position:absolute;left:15px;top:1rem}.docs-logo-wrapper .site-logo{display:inline-block}.docs-top-utilities{padding-top:12px}.docs-sidebar-toggler{display:inline-block;border:none;padding:0;font-size:inherit;position:relative;top:.3rem;background:0 0}.docs-sidebar-toggler:focus{outline:0}.docs-sidebar-toggler:hover span{-webkit-opacity:1;-moz-opacity:1;opacity:1}.docs-sidebar-toggler span{display:block;background-color:#252930;height:3px;width:24px;margin-top:5px;margin-bottom:5px;position:relative;left:0;-webkit-opacity:.8;-moz-opacity:.8;opacity:.8;border-radius:1px}.docs-wrapper{position:relative}.docs-sidebar{display:none;width:400px;position:fixed;z-index:10;top:69px;height:calc(100% - 69px);background:#fff;overflow-y:auto;scrollbar-color:rgba(0,0,0,.2) #f5f5f5;scrollbar-width:thin;transition:-webkit-transform .35s ease-in-out;transition:transform .35s ease-in-out;transition:transform .35s ease-in-out,-webkit-transform .35s ease-in-out;box-shadow:1px 0 5px 0 rgba(0,0,0,.1)}.docs-sidebar::-webkit-scrollbar{width:6px;background-color:#f5f5f5}.docs-sidebar::-webkit-scrollbar-thumb{background-color:rgba(0,0,0,.125);border-radius:.5rem}@media (prefers-reduced-motion:reduce){.docs-sidebar{transition:none}}.docs-sidebar.sidebar-visible{-webkit-transform:translateX(0);transform:translateX(0);display:block}.docs-sidebar.sidebar-hidden{-webkit-transform:translateX(-400px);transform:translateX(-400px);display:block}.docs-nav{overflow-y:auto;padding:1rem}.docs-nav .section-title{font-size:1rem;margin-bottom:1rem}.docs-nav .section-title a:hover{text-decoration:none}.docs-nav .section-items{font-size:.875rem;position:relative}.docs-nav .nav-item{margin-left:2.5rem}.docs-nav .nav-item.section-title{margin-left:0}.docs-nav .nav-item.section-title .nav-link{padding:0}.docs-nav .nav-item.section-title .nav-link:before{display:none}.docs-nav .nav-item.active .nav-link{color:#28b76b}.docs-nav .nav-item.active .nav-link:before{background-color:#28b76b}.docs-nav .nav-item.active .nav-link .theme-icon-holder{color:#fff;background:#28b76b}.docs-nav .nav-link{display:inline-block;position:relative;padding:.5rem 1rem;color:#5d6778}.docs-nav .nav-link .theme-icon-holder{font-size:.875rem;padding-top:.375rem}.docs-nav .nav-link.active{color:#28b76b}.docs-nav .nav-link.active:before{background-color:#28b76b}.docs-nav .nav-link.active .theme-icon-holder{color:#fff;background:#28b76b}.docs-nav .nav-link:before{background-color:#f4fcf6;content:' ';display:inline-block;height:inherit;left:0;margin-top:-.5rem;position:absolute;width:3px;height:100%;border-radius:1rem}.docs-content{margin-left:300px;padding-bottom:500px}.docs-article{padding:2rem;color:#5d6778;scroll-margin-top:69px;scroll-snap-margin-top:69px}.docs-article strong{color:#252930}.docs-article .docs-heading{font-size:2.5rem;margin-bottom:2rem;position:relative}.docs-section .docs-time{display:inline-block;right:0;bottom:1rem;font-size:.75rem;font-weight:400;color:#747f94}.docs-article .docs-section{padding:2rem 0;border-bottom:1px solid #e7e9ed;scroll-margin-top:69px;scroll-snap-margin-top:69px}.docs-article .docs-section p:last-child{margin-bottom:0}.docs-article .section-heading{font-size:1.875rem;margin-bottom:1rem;color:#252930;word-wrap:break-word}.docs-article .h2,.docs-article h2{color:#464e5b}.docs-article .h3,.docs-article h3{font-size:1.5rem;color:#464e5b}.docs-article .h4,.docs-article h4{font-size:1.25rem;color:#464e5b}.docs-article .h5,.docs-article h5{font-size:1rem;color:#464e5b}.docs-article .h6,.docs-article h6{font-size:.875rem;color:#464e5b}.docs-article dl,.docs-article ol,.docs-article ul{padding-left:1.5rem}.docs-article li{padding-top:.5rem;padding-bottom:.5rem}.docs-code-block{padding-top:1rem;padding-bottom:1rem}.callout-block{padding:1.5rem;border-left:3px solid #5d6778;background:#f5f5f5;margin-top:1rem;margin-bottom:1rem}.callout-block code{background:#fff}.callout-block .callout-title{font-size:1rem}.callout-block.callout-block-info{border-color:#5b99ea;background:#f9fbfe}.callout-block.callout-block-info .callout-title{color:#1c6fdc}.callout-block.callout-block-info a{color:#1c6fdc}.callout-block.callout-block-success{border-color:#5cb377;background:#e7f4eb}.callout-block.callout-block-success .callout-title{color:#3e8554}.callout-block.callout-block-success a{color:#3e8554}.callout-block.callout-block-warning{border-color:#eebf41;background:#fdf6e5}.callout-block.callout-block-warning .callout-title{color:#d09c13}.callout-block.callout-block-warning a{color:#d09c13}.callout-block.callout-block-danger{border-color:#d26d69;background:#fbf3f2}.callout-block.callout-block-danger .callout-title{color:#b73c37}.callout-block.callout-block-danger a{color:#b73c37}.cta-section .container{position:relative;z-index:10}@media print{#docs-sidebar{display:none!important}}@media (max-width:767.98px){.docs-article .docs-heading{font-size:2.25rem}.docs-article .section-heading{font-size:1.5rem}}@media (max-width:1199.98px){.docs-content{margin-left:0}.docs-article .docs-time{position:static;display:block;padding-top:.5rem}}
            </style>

        </head>

        <body class="docs-page">
            <header class="header fixed-top">
                <div class="branding docs-branding">
                    <div class="container-fluid position-relative py-2">
                        <div class="docs-logo-wrapper">

        	                <div class="site-logo"><span class="logo-text">One Page<span class="text-alt"> Layer Catalogue</span></span></a></div>
                        </div><!--//docs-logo-wrapper-->
        	            <div class="docs-top-utilities d-flex justify-content-end align-items-center">


        					<ul class="social-list list-inline mx-md-3 mx-lg-5 mb-0 d-none d-lg-flex">
        						<span class="org-text">$(ArcGIS_URL)</span>
        		            </ul><!--//social-list-->
        	            </div><!--//docs-top-utilities-->
                    </div><!--//container-->
                </div><!--//branding-->
            </header><!--//header-->
      SET_TO type = html
    -> Aggregator_6
AttributeManager
    ATTR_TABLE:
      REMOVE _creation_instance
      REMOVE _headers{}.name
      REMOVE _headers{}.value
      RENAME_SET_VALUE _response_body > Token
      REMOVE _http_status_code
      REMOVE json_type
      REMOVE json_index
      SET_TO Content Query = $(ArcGIS_URL)/sharing/rest/search
      SET_TO Query Parameters = token=@Value(Token)&f=json&q=$(Query)&sortField=numviews&sortOrder=desc&start=0&num=10000
    -> HTTPCaller_2
Note: Query user's content
HTTPCaller_2
    CONNECTION_TIMEOUT_LENGTH = 60
    ERROR_ATTR = _error
    FOLLOW_REDIRECTS = FOLLOW_WITH_ORIGINAL_METHOD
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_HEADER_LIST_ATTR = _headers
    RESPONSE_TYPE = Attribute
    SPLIT_MULTIPART_DOWNLOADS = NO
    STATUS_CODE_ATTR = _http_status_code
    TARGET_ATTR = _response_body
    TARGET_ATTR_ENCODING = auto-detect
    TARGET_URL = @Value(Content Query)
    TRANSFER_TIMEOUT_LENGTH = 90
    UPLOAD_BODY = @Value(Query Parameters)
    UPLOAD_CONTENT_TYPE = URL Encoded (application/x-www-form-urlencoded)
    UPLOAD_TYPE = Specify Upload Body
    USE_COOKIES = No
    VERIFY_SSL_CERTIFICATES = Yes
    -> JSONFlattener
Note: Flatten JSON and expose item attributes
JSONFlattener
    ERROR_LIST_ATTR = _json_error
    JSON_DOCUMENT = @Value(_response_body)
    NEW_ATTRIBUTES = results{}.id results{}.owner results{}.title results{}.type results{}.modified results{}.title results{}.snippet results{}.description results{}.tags{} results{}.categories{} results{}.accessInformation results{}.url results{}.contentStatus results{}.access
    READ_FROM_FILE = NO
    RECURSIVE = Yes
    -> ListExploder
ListExploder
    ATTR_ACCUM_MODE = Merge List Attributes
    ATTR_CONFLICT_RES = Use List Attribute Values
    INDEX_ATTR = _element_index
    LIST_ATTR = results{}
    ELEMENTS -> ListExploder_2
Note: Explode Categories
ListExploder_2
    ATTR_ACCUM_MODE = Merge List Attributes
    ATTR_CONFLICT_RES = Use List Attribute Values
    INDEX_ATTR = _element_index
    LIST_ATTR = categories{}
    ELEMENTS -> AttributeSplitter
AttributeSplitter
    ATTR_NAME = categories
    DELIMITER = /
    DROP_EMPTY_PARTS = No
    LIST_NAME = _categories_list
    TRIM_OPTION = Both
    -> AttributeManager_4
AttributeManager_3
    ATTR_TABLE:
      REMOVE Token
      REMOVE Content Query
      REMOVE Query Parameters
      REMOVE _headers{}.name
      REMOVE _headers{}.value
      REMOVE _response_body
      REMOVE _http_status_code
      REMOVE owner
      RENAME_SET_VALUE title > Title
      RENAME_SET_VALUE type > Type
      RENAME_SET_VALUE modified > Modified
      RENAME_SET_VALUE snippet > ShortDescription
      REMOVE description
      REMOVE tags{}
      REMOVE categories
      RENAME_SET_VALUE accessInformation > Credits
      RENAME_SET_VALUE access > Access = @FullTitleCase(@Value(Access))
      REMOVE _element_index
      SET_TO Category = @Value(_categories_list{2})
      SET_TO itemHref = @ReplaceString(@Value(Title), ,_,caseSensitive=TRUE)
      SET_TO categoryHref = @ReplaceString(@Value(Category), ,_,caseSensitive=TRUE)
      SET_TO _itemLinks = <li class="nav-item"><a class="nav-link scrollto" href="#@Value(itemHref)">@Value(Title)</a></li>
      SET_TO _categoryLinks = <li class="nav-item section-title"><a class="nav-link scrollto" href="#@Value(categoryHref)"><span class="theme-icon-holder me-2"><i class="fas fa-map-signs"></i></span>@Value(Category)</a></li>
      SET_TO _itemSections = <section class="docs-section" id="@Value(itemHref)">
            <h2 class="section-heading">@Value(Title) <span class="docs-time">Last updated: @Value(Modified)</span></h2>
                <p><code>@Value(Access)</code> <code>@Value(Type)</code></p>
        						<p>@Value(ShortDescription)</p>
        						<p><strong>Credits (Attribution): </strong>@Value(Credits)</p>

        						<a href="$(ArcGIS_URL)/home/item.html?id=@Value(id)#overview" target="_blank">Go to item</a>

        					</section><!--//section-->
      SET_TO _itemSectionHeaders = <article class="docs-article" id="@Value(categoryHref)">
            <header class="docs-header">
        		<h1 class="docs-heading">@Value(Category) </h1>
        	</header>
    -> Sorter
Sorter
    SORT_PARM = Category NATURAL ASCENDING Title NATURAL ASCENDING
    SORTED -> Aggregator
    SORTED -> Aggregator_2
AttributeManager_5
    ATTR_TABLE:
      SET_TO doc_nav = <div class="docs-wrapper">
        	    <div id="docs-sidebar" class="docs-sidebar">
        		    <nav id="docs-nav" class="docs-nav navbar">
        			    <ul class="section-items list-unstyled nav flex-column pb-3">
                            <!--Nav Content from FME-->
                            @Value(_itemNav)
        				    <!--End of Nav Content from FME-->
        			    </ul>

        		    </nav><!--//docs-nav-->
        	    </div><!--//docs-sidebar-->
      SET_TO type = html
    -> Aggregator_6
AttributeManager_8
    ATTR_TABLE:
      SET_TO doc_article = <div class="docs-content">
        		    <div class="container">
                    <!--Article sections from FME-->
                    @Value(_arcticleSections)
                    <!--End of Article sections from FME-->
      SET_TO type = html
    -> Aggregator_6
Note: set doc footer
AttributeManager_9
    ATTR_TABLE:
      SET_TO doc_footer = <footer class="footer">
        				    <div class="container text-center py-5">
        			            <small class="copyright">One Page Layer Catalogue for ArcGIS Online or ArcGIS Enterprise Portal Items. Produced from FME Workbench using ArcGIS
            REST API.</small>

        				    </div>
        			    </footer>
        		    </div>
        	    </div>
            </div><!--//docs-wrapper-->





            <!-- Page Specific JS -->


            <script>
        		"use strict";const sidebarToggler=document.getElementById("docs-sidebar-toggler"),sidebar=document.getElementById("docs-sidebar"),sidebarLinks=document.querySelectorAll("#docs-sidebar .scrollto");function responsiveSidebar(){window.innerWidth>=1200?(console.log("larger"),sidebar.classList.remove("sidebar-hidden"),sidebar.classList.add("sidebar-visible")):(console.log("smaller"),sidebar.classList.remove("sidebar-visible"),sidebar.classList.add("sidebar-hidden"))}window.onload=function(){responsiveSidebar()},window.onresize=function(){responsiveSidebar()},sidebarToggler.addEventListener("click",()=>{sidebar.classList.contains("sidebar-visible")?(console.log("visible"),sidebar.classList.remove("sidebar-visible"),sidebar.classList.add("sidebar-hidden")):(console.log("hidden"),sidebar.classList.remove("sidebar-hidden"),sidebar.classList.add("sidebar-visible"))}),sidebarLinks.forEach(a=>{a.addEventListener("click",b=>{b.preventDefault();var c=a.getAttribute("href").replace("#","");document.getElementById(c).scrollIntoView({behavior:"smooth"}),sidebar.classList.contains("sidebar-visible")&&window.innerWidth<1200&&(sidebar.classList.remove("sidebar-visible"),sidebar.classList.add("sidebar-hidden"))})});var spy=new Gumshoe("#docs-nav a",{offset:69}),lightbox=new SimpleLightbox(".simplelightbox-gallery a",{})
        	</script>

        </body>
        </html>

      SET_TO type = html
    -> Aggregator_6
Aggregator_6
    ACCUM_ATTRS_NAME = Merge Incoming Attributes
    GROUP_BY = type
    MODE = Attributes Only
    AGGREGATE -> AttributeManager_10
AttributeManager_10
    ATTR_TABLE:
      SET_TO html_content = @Value(doc_header)
        @Value(doc_nav)
        @Value(doc_article)
        @Value(doc_footer)
    -> HTML (writer HTML_1)
HTML (writer HTML_1)
    attributes: html_content buffer

Bookmark: Request and extract token from ArcGIS Online or Portal
HTTPCaller
    ADDITIONAL_URL_PARAMETERS = client;referer expiration;60 f;json referer;https://arcgis.com
    CONNECTION_TIMEOUT_LENGTH = 60
    ERROR_ATTR = _error
    FOLLOW_REDIRECTS = FOLLOW_WITH_ORIGINAL_METHOD
    HTTP_METHOD = POST
    MAX_HTTP_VERSION = HTTP_2
    MAX_TRANSFERS_IN_PROGRESS = 25
    MINIMUM_ENCRYPTION_LEVEL = OS_DEFAULT
    MULTIPARTS = username StringUpload SOURCE_EXPRESSION;$(Username);MIME_TYPE;text/plain;FME_CONTROLLER_QUERY_FILE;transformers\dependencies\http\StringUpload.fme;FME_CONTROLLER_CHOICE;StringUpload password StringUpload SOURCE_EXPRESSION;$(Password);MIME_TYPE;text/plain;FME_CONTROLLER_QUERY_FILE;transformers\dependencies\http\StringUpload.fme;FME_CONTROLLER_CHOICE;StringUpload
    REDIRECT_AUTH = ORIGINAL_DOMAIN_ONLY
    RESPONSE_HEADER_LIST_ATTR = _headers
    RESPONSE_TYPE = Attribute
    SPLIT_MULTIPART_DOWNLOADS = NO
    STATUS_CODE_ATTR = _http_status_code
    TARGET_ATTR = _response_body
    TARGET_ATTR_ENCODING = auto-detect
    TARGET_URL = https://arcgis.com/sharing/rest/generateToken?
    TRANSFER_TIMEOUT_LENGTH = 90
    UPLOAD_TYPE = Multipart / Form Data
    USE_COOKIES = No
    VERIFY_SSL_CERTIFICATES = Yes
    -> JSONFragmenter
HTTPCaller_3
    ADDITIONAL_URL_PARAMETERS = client;referer expiration;86400 f;json referer;https://arcgis.com
    CONNECTION_TIMEOUT_LENGTH = 60
    ERROR_ATTR = _error
    FOLLOW_REDIRECTS = Yes
    HTTP_METHOD = POST
    MULTIPARTS = username StringUpload SOURCE_EXPRESSION;$(Username);MIME_TYPE;text/plain;FME_CONTROLLER_QUERY_FILE;transformers\dependencies\http\StringUpload.fme;FME_CONTROLLER_CHOICE;StringUpload password StringUpload SOURCE_EXPRESSION;$(Password);MIME_TYPE;text/plain;FME_CONTROLLER_QUERY_FILE;transformers\dependencies\http\StringUpload.fme;FME_CONTROLLER_CHOICE;StringUpload
    RESPONSE_HEADER_LIST_ATTR = _headers
    SAVE_FILE = Attribute
    STATUS_CODE_ATTR = _http_status_code
    TARGET_ATTR = _response_body
    TARGET_ATTR_ENCODING = auto-detect
    TARGET_URL = $(ArcGIS_URL)/sharing/rest/generateToken?
    TRANSFER_TIMEOUT_LENGTH = 90
    UPLOAD_TYPE = Multipart / Form Data
    USE_COOKIES = No
    VERIFY_SSL_CERTIFICATES = Yes
    -> JSONFragmenter
JSONFragmenter
    EXPLODE_FORMAT = JSON
    EXTRACT_ATTR = No
    JSON_ATTR = _response_body
    JSON_QUERY = json["token"]
    READ_FROM_FILE = NO
    REJECT_EMPTY_LISTS = YES
    FRAGMENTS -> AttributeManager

Bookmark: Convert UNIX time
AttributeManager_4
    ATTR_TABLE = SET_TO modified = @Evaluate(@Value(modified)/1000)
    -> DateTimeConverter
DateTimeConverter
    DATETIME_ATTR = modified
    IN_FORMAT = %Es$
    OUT_FORMAT = %Y-%m-%d
    PASSTHROUGH = NO
    REPAIR_INPUT = YES
    -> AttributeManager_3

Bookmark: Nav Content
Aggregator
    ACCUM_ATTRS_NAME = Drop Incoming Attributes
    AGGREGATE_TYPE = Homogeneous Collection (If Possible)
    CONCAT_ATTRS = _itemLinks
    GROUP_BY = _categoryLinks
    MODE = Geometry - Assemble One Level
    AGGREGATE -> AttributeManager_6
AttributeManager_6
    ATTR_TABLE:
      SET_TO _itemNav = @Value(_categoryLinks)
        @Value(_itemLinks)
    -> Aggregator_3
Aggregator_3
    ACCUM_ATTRS_NAME = Drop Incoming Attributes
    AGGREGATE_TYPE = Homogeneous Collection (If Possible)
    CONCAT_ATTRS = _itemNav
    MODE = Geometry - Assemble One Level
    AGGREGATE -> AttributeManager_5

Bookmark: Article Content
Aggregator_2
    ACCUM_ATTRS_NAME = Drop Incoming Attributes
    AGGREGATE_TYPE = Homogeneous Collection (If Possible)
    CONCAT_ATTRS = _itemSections
    GROUP_BY = _itemSectionHeaders
    MODE = Geometry - Assemble One Level
    AGGREGATE -> AttributeManager_7
AttributeManager_7
    ATTR_TABLE:
      SET_TO _arcticleSections = @Value(_itemSectionHeaders)
        @Value(_itemSections)
        </article>
    -> Aggregator_4
Aggregator_4
    ACCUM_ATTRS_NAME = Drop Incoming Attributes
    AGGREGATE_TYPE = Homogeneous Collection (If Possible)
    CONCAT_ATTRS = _arcticleSections
    MODE = Geometry - Assemble One Level
    AGGREGATE -> AttributeManager_8
